/*
Copyright (C) 2013-2018 Huawei Technologies Co., Ltd. All rights reserved.
*/
module test-duplicate-old-enum-name-value {
  namespace "http://www.huawei.com/netconf/vrp/test-duplicate-old-enum-name-value";
  prefix old_enum_name_value;
  organization
    "Huawei Technologies Co., Ltd.";
  contact
    "Huawei Industrial Base Bantian, Longgang Shenzhen 518129                    
        People's Republic of China                    
        Website: http://www.huawei.com Email: support@huawei.com";
  description
    "Security management, which includes the management on authentication, authorization, accounting, domains, and users.";
  revision 2018-06-11 {
    description
      "The modifications in the schema file are synchronized to the YANG file.";
    reference
      "Huawei private.";
  }
  
  typedef statusType {
    type enumeration {
      enum "a" {
        description
          "Blocked state.";
          value 5;
      }
      enum "b" {
        description
          "Activated state.";
          value 6;
      }
      enum "c" {
        description
          "Blocked state.";
          value 7;
      }
      enum "d" {
        description
          "Activated state.";
          value 6;
      }
    }
    description
      "";
  }
  
  container aaa {
    description
      "Security management, which includes the management on authentication, authorization, accounting, domains, and users.";
      
      leaf current-status{
        type statusType;
        description "current status";
      }
  }
}
