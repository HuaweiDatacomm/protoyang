/*
Copyright (C) 2013-2018 Huawei Technologies Co., Ltd. All rights reserved.
*/
module huawei-pub-type {
  namespace "http://www.huawei.com/netconf/vrp/huawei-pub-type";
  prefix pub-type;
  import huawei-extension {
    prefix ext;
  }
  organization
    "Huawei Technologies Co., Ltd.";
  contact
    "Huawei Industrial Base Bantian, Longgang Shenzhen 518129                    
        People's Republic of China                    
        Website: http://www.huawei.com Email: support@huawei.com";
  description
    "pub type";
  revision 2018-06-11 {
    description
      "The modifications in the schema file are synchronized to the YANG file.";
    reference
      "Huawei private.";
  }
  revision 2017-12-23 {
    description
      "The modifications in the schema file are synchronized to the YANG file.";
    reference
      "Huawei private.";
  }
  revision 2017-03-23 {
    description
      "Functions supported by the schema are added to the YANG file.";
    reference
      "Huawei private.";
  }
  revision 2013-01-01 {
    description
      "Init revision";
    reference
      "Huawei private.";
  }
  typedef editOperationType {
    type enumeration {
      enum "merge" {
        description
          "";
      }
      enum "replace" {
        description
          "";
      }
      enum "create" {
        description
          "";
      }
      enum "delete" {
        description
          "";
      }
    }
    description
      "editOperationType";
  }

  typedef timeZone {
    type string {
      length "0..15";
    }
    description
      "timeZone is like +08:00";
  }

  typedef time_hhmm {
    type string {
      length "5";
      pattern '(([0-1][0-9])|(2[0-3])):[0-5][0-9]';
    }
    description
      "time_hhmm is like string";
  }

  typedef macAddress {
    type string {
      length "0..255";
    }
    description
      "A MAC address in standard notation";
  }

  typedef ipv4PrefixLength {
    type uint32 {
      range "0..32";
    }
    description
      "An IPv4 address prefix length. Must lie between 0 and 32 inclusive.";
  }

  typedef ipv6PrefixLength {
    type uint32 {
      range "0..128";
    }
    description
      "An IPv6 address prefix length. Must lie between 0 and 128 inclusive.";
  }

  typedef ipv4AddressPrefix {
    type string {
      length "0..255";
    }
    description
      "now ipv4AddressPrefix is like string";
  }

  typedef ipv6AddressPrefix {
    type string {
      length "0..255";
    }
    description
      "now ipv6AddressPrefix is like string";
  }

  typedef block {
    type string {
      length "0..255";
    }
    description
      "now block is like string";
  }

  typedef oid {
    type string {
      length "0..255";
    }
    description
      "now oid is like string";
  }

  typedef data {
    type string {
      length "0..255";
    }
    description
      "now data is like string";
  }

  typedef chassisPath {
    type uint32 {
      range "0..127";
    }
    description
      "chassisPath is an unsignedInt";
  }

  typedef slotPath {
    type string {
      length "1..127";
      pattern '\d+/\d+';
    }
    description
      "slotPath is like 1/1";
  }

  typedef cardPath {
    type string {
      length "1..127";
    }
    description
      "cardPath";
  }

  typedef valspBitErrString {
    type string {
      length "1..63";
    }
    description
      "biError is like 0";
  }

  typedef ifNameString {
    type string {
      length "1..63";
    }
    description
      "ifName is like ethernet1/1/1/1";
  }

  typedef ifName {
    type ifNameString;
    description
      "ifName";
  }

  typedef vrfNameExt {
    type vrfName;
    description
      "vrfNameExt";
  }

  typedef positionString {
    type string {
      length "1..32";
    }
    description
      "board position is like [1], serialPort position is like[1/1/1/1:2:3]";
  }

  typedef position {
    type positionString;
    description
      "position";
  }

  typedef password {
    type string {
      length "1..128";
    }
    description
      "The password is a string ranging from 1 to 16 characters for a plaintext password and 20 to 128 characters for a ciphertext password.";
  }

  typedef passwordOSPF {
    type string {
      length "1..8";
    }
    description
      "now password is like string";
  }

  typedef passwordExtend {
    type string {
      length "1..432";
    }
    description
      "The password is a string ranging from 1 to 255 characters for a plaintext password and 20 to 432 characters for a ciphertext password.";
  }

  typedef oneInputPasswordExtend {
    type string {
      length "1..255";
    }
    description
      "now oneInputPasswordExtend is like string, only input once no need to confirm";
  }

  typedef mibString {
    type string {
      length "0..255";
    }
    description
      "now mibString is like string";
  }

  typedef vrfName {
    type string {
      length "1..31";
    }
    description
      "now vrfName is like string";
  }

  typedef keyChainName {
    type string {
      length "0..47";
    }
    description
      "now keyChainName is like string";
  }

  typedef ipv4Mask {
    type string {
      length "1..255";
    }
    description
      "ipv4Mask support both mask and length format";
  }

  typedef ipv6Mask {
    type string {
      length "0..255";
    }
    description
      "ipv6Mask support both mask and length format";
  }

  typedef timeTick {
    type uint32;
    description
      "timeTick is like unsignedInt";
  }

  typedef identifierString {
    type string {
      pattern '([^\s?|>]*)';
    }
    description
      "now identifierString is like string, which is used for identifier with strict limitation";
  }

  typedef descriptionString {
    type string {
      pattern '([^?]*)';
    }
    description
      "now descriptionString is like string, which is used for description with little limitation";
  }

  typedef rowStatus {
    type enumeration {
      enum "active" {
        description
          "Rule status is active at the current time.";
      }
      enum "notInService" {
        description
          "Rule status is not active at the current time.";
      }
      enum "notReady" {
        description
          "The system is unavailable at the moment.";
      }
    }
    description
      "rowStatus is like string";
  }

  typedef bits8 {
    type uint8;
    description
      "bits8 is like unsignedByte";
  }

  typedef bits16 {
    type uint16;
    description
      "bits16 is like unsignedShort";
  }

  typedef bits32 {
    type uint32;
    description
      "bits32 is like unsignedInt";
  }

  typedef bits64 {
    type uint64;
    description
      "bits64 is like unsignedLong";
  }

  typedef percent {
    type uint8 {
      range "0..100";
    }
    description
      "percent is like unsignedByte";
  }

  typedef bandWidth {
    type uint64;
    description
      "Type of ifOperSpeed";
  }

  typedef appType {
    type enumeration {
      enum "lct" {
        description
          "LCT";
      }
      enum "ems" {
        description
          "EMS";
      }
      enum "cmd" {
        description
          "CMD";
      }
      enum "ftp" {
        description
          "FTP";
      }
      enum "unknown" {
        description
          "UNKNOWN";
      }
    }
    description
      "";
  }

  typedef teTnlName {
    type string {
      length "1..35";
      pattern '[^ ]*';
    }
    description
      "TE tunnel name";
  }

  typedef evpnName {
    type string {
      length "1..31";
    }
    description
      "now evpnName is like string";
  }

  typedef teTnlNameExt {
    type teTnlName;
    description
      "teTnlNameExt";
  }

  typedef devmTimeslotListType {
    type string {
      length "1..61";
    }
    description
      "";
  }

  typedef hostName {
    type string {
      length "1..255";
    }
    description
      "";
  }

  typedef XplFilterName {
    type string {
      length "1..585";
      pattern '^\s*(([0-9a-zA-Z][0-9a-zA-Z\-_\.]{0,63})|([0-9a-zA-Z][0-9a-zA-Z\-_\.]{0,63}[\(](($)?[0-9a-zA-Z][0-9a-zA-Z\-_\.]{0,63})(([,]($)?[0-9a-zA-Z][0-9a-zA-Z\-_\.]{0,63}){0,7})[\)]))\s*';
    }
    description
      "";
  }

  typedef passwordIke {
    type string {
      length "1..127";
    }
    description
      "now passwordIke is like string";
  }

  typedef aclNumOrName {
    type string {
      length "1..64";
      pattern '([1-9]\d{3})|(10[0-9]{3})|(23[0-9]{3})|(99999)|([0-9a-zA-Z]([^\s]*))';
    }
    description
      "aclNumOrName is begin with a-z or A-Z or 0-9";
  }

  typedef hexBinary {
    type string {
      length "1..10";
      pattern '(0x|0X)?[0-9a-fA-F]+';
    }
    description
      "This is a hexadecimal variable.";
  }

  typedef date {
    type string {
      pattern '\d{4}-\d{2}-\d{2}';
    }
    description
      "XSD date string type.";
    reference "http://www.w3.org/TR/2004/REC-xmlschema-2-20041028/datatypes.html#date";
  }

  typedef time {
    type string {
      pattern '\d{2}:\d{2}:\d{2}';
    }
    description
      "XSD time string type.";
    reference "http://www.w3.org/TR/2004/REC-xmlschema-2-20041028/datatypes.html#date";
  }
    typedef id-range {
    type string {
      pattern '([0-9]|,|\+|\-|\(|\))+';
	}
    description
      "id list,such as '1,3,5-7',or '+1,-3,+(20-30)'.";
  }
  typedef vlan-range {
    type id-range {
      pattern '((409[0-4]|40[0-8][0-9]|[1-3][0-9]{3}|[1-9][0-9]{1,2}|[1-9])?(-(409[0-4]|40[0-8][0-9]|[1-3][0-9]{3}|[1-9][0-9]{1,2}|[1-9]))?(,((409[0-4]|40[0-8][0-9]|[1-3][0-9]{3}|[1-9][0-9]{1,2}|[1-9])(-(409[0-4]|40[0-8][0-9]|[1-3][0-9]{3}|[1-9][0-9]{1,2}|[1-9]))?))*)|((([\\+|\\-](409[0-4]|40[0-8][0-9]|[1-3][0-9]{3}|[1-9][0-9]{1,2}|[1-9]))|([\\+|\\-]\\((409[0-4]|40[0-8][0-9]|[1-3][0-9]{3}|[1-9][0-9]{1,2}|[1-9])-(409[0-4]|40[0-8][0-9]|[1-3][0-9]{3}|[1-9][0-9]{1,2}|[1-9])\\)))?(,(([\\+|\\-](409[0-4]|40[0-8][0-9]|[1-3][0-9]{3}|[1-9][0-9]{1,2}|[1-9]))|([\\+|\\-]\\((409[0-4]|40[0-8][0-9]|[1-3][0-9]{3}|[1-9][0-9]{1,2}|[1-9])-(409[0-4]|40[0-8][0-9]|[1-3][0-9]{3}|[1-9][0-9]{1,2}|[1-9])\\))))*)';
      ext:value-range "1..4094";
    }
    description
      "vlan id list,the value is 1-4094.";
  }
}
