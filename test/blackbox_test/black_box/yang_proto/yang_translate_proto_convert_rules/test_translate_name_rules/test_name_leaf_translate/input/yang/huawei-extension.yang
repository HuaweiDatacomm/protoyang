/*
Copyright (C) 2013-2018 Huawei Technologies Co., Ltd. All rights reserved.
*/
module huawei-extension {
  namespace "http://www.huawei.com/netconf/vrp/huawei-extension";
  prefix ext;

  organization
    "Huawei Technologies Co., Ltd.";
  contact
    "Huawei Industrial Base
     Bantian, Longgang
     Shenzhen 518129
     People's Republic of China
     Website: http://www.huawei.com
     Email: support@huawei.com";
  description
    "ac ne extension yang syntax";
  revision 2018-06-11 {
    description
      "The modifications in the schema file are synchronized to the YANG file.";
    reference
      "Huawei private.";
  }
  revision 2017-12-23 {
    description
      "The modifications in the schema file are synchronized to the YANG file.";
    reference
      "Huawei private.";
  }
  revision 2017-03-23 {
    description
      "Functions supported by the schema are added to the YANG file.";
    reference
      "Huawei private.";
  }
  revision 2013-01-01 {
    description
      "Init revision";
    reference
      "Huawei private.";
  }
  extension support-filter {
    argument value;
    description
      "support-filter";
  }

  extension value-mapping {
    description
      "value-mapping";
  }

  extension value-replace {
    description
      "value-replace";
  }

  extension item {
    argument value;
    description
      "item";
  }

  extension meaning {
    argument value;
    description
      "meaning";
  }

  extension case-sensitivity {
    argument value;
    description
      "case-sensitivity ";
  }

  extension bitmap-bit-range {
    argument value;
    description
      "bitmap-bit-range";
  }

  extension masklen {
    argument value;
    description
      "masklen";
  }

  extension bit {
    argument value;
    description
      "bit";
  }

  extension allowDelete {
    argument value;
    description
      "allowDelete";
  }
  extension value-range {
    argument value;
    description
      " The range of values that can be entered using the id-range type or its derived type node. ";
  }
  
  extension task-name {
    argument value;
    description
      "task-name";
  }
  
  extension entry-from {
    argument value;
    description "Applies only to a list or presence container whose config is true. " +
      "entry-from specifies an instance to be automatically generated by the system "+
	  "based on other data or to be created by a user.";
  }
  
  extension node-ref {
	argument value;
	description 
      "Indicates the XPath of the data node for which the rpc operation is performed. "+
      "If the rpc operation is performed for the entire system (the corresponding node "+
      "cannot be found in the model tree), this syntax is not required.";
  }
  
}
